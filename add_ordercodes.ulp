#require 6.0000

string tr(string s)
{
    return s;
}


if (!schematic)
{
  dlgMessageBox (usage + tr ("<hr><b>ERROR: No schematic!</b><p>\nThis program can only work in"
                 " the schematic editor."));
  exit (1);
}


int RefDefsColumn = 0;
string csvPath;
int ocsSize = 0;
string ocNames[];
int ocIndexes[];
int selectedSeparatorIndex = 1;
string separators[] = { tr("comma"), tr("semicolon"), tr("tabulator")};

      
string StripWhiteSpace (string s)
{
  while (s && isspace (s [0]))
    s = strsub (s, 1);
  while (s && isspace (s [strlen (s) - 1]))
    s = strsub (s, 0, strlen (s) - 1);
  return s;
}

int findSheetIndex(string refdef)
{
    schematic(S) {
        S.parts(P) {
            P.instances(I) {
                if (P.name == refdef)
                    return I.sheet;
            }
        }
    } 
    return -1;
}

string import(string csvPath, int selectedSeparatorIndex, int refdefsIndex)
{
    string ret = "";
    string lines[];
    int CSVSeparator = 0;
    int nLines = fileread(lines, csvPath);
    string cols[];
    int sheetIndex = -1;
    
    switch (selectedSeparatorIndex) {
    case 0:
      CSVSeparator = ',';
      break;
    case 1:
      CSVSeparator = ';';
      break;          
    case 2:
      CSVSeparator = '\t';
      break;          
    }
    
    for (int lineIndex = 0; lineIndex < nLines; lineIndex++) {
        int colC = 0;
        if (CSVSeparator == ',') {
            
        } else {
            colC = strsplit(cols, lines[lineIndex], CSVSeparator);
        }
        if (lineIndex == 0) {
            // first line shall contain the OC_fields
            for (int col = 0; col<colC; col++) {
                string prefix = strsub(cols[col], 0, 3);
                if (prefix == "OC_" || prefix == "oc_") {
                    ocNames[ocsSize] = cols[col];
                    ocIndexes[ocsSize] = col;
                    ocsSize++;
                    printf("Oredercode column found in %d col\n", col);
                }
            }
        } else {
            string refdefs[];
            int refdefsC = strsplit(refdefs, cols[refdefsIndex], ','); 
            for (int ri = 0; ri<refdefsC; ri++) {
                string refdes = StripWhiteSpace(refdefs[ri]);
                if (refdes == "")
                    continue;
                printf("Looking ordercodes for %s\n", refdes);
                for (int ocIndex = 0; ocIndex < ocsSize; ocIndex++) {
                    printf("OC in col %d == %s\n", ocIndexes[ocIndex], cols[ocIndexes[ocIndex]]);
                    if (cols[ocIndexes[ocIndex]] != "") {
                        int sheetIndexTmp = findSheetIndex(refdes);
                        if (sheetIndexTmp != -1) {
                            if (sheetIndexTmp != sheetIndex)
                                sprintf(ret, "%sEDIT .s%d;\n", ret, sheetIndexTmp);
                            sheetIndex = sheetIndexTmp;
                            sprintf(ret, "%sCHANGE DISPLAY OFF;\n", ret);
                            sprintf(ret, "%sATTRIBUTE %s %s '%s';\n", ret, refdes, ocNames[ocIndex], cols[ocIndexes[ocIndex]]);
                        } else {
                            printf("Unable to find part %s\n", refdes);
                        }
                    }
                }
            }
        }
    }
    printf(ret);
    return ret;
}

output("/tmp/test.txt", "wt") {

dlgDialog (tr ("Import ordercodes from Bill Of Material"))
{
    dlgLabel(tr("This ULP requires a CSV file (exported by bom_w_attr.ulp for e.g.).\n"
    "The script will pull the attributes from columns named OC_* and add it to the devices in the schematic."));
    dlgGroup (tr ("BoM file"))
    {
        dlgStringEdit (csvPath);
        dlgPushButton("Browse") {
            csvPath = dlgFileOpen("Select the BoM file", "", "*.csv"); 
        }
    }
  dlgHBoxLayout
  {
    dlgGroup (tr ("Reference designators colum (0 based)"))
    {
      // TODO create a dlgComboBox with A-Z...
      dlgSpinBox (RefDefsColumn);
    }
    dlgGroup (tr ("Column separator"))
    {
      dlgComboBox(separators, selectedSeparatorIndex);
    }
    dlgStretch (1);
  }
  dlgHBoxLayout
  {
    dlgStretch (1);
    dlgPushButton (tr ("Import")) exit(import(csvPath, selectedSeparatorIndex, RefDefsColumn));
    dlgPushButton (tr ("-Close")) dlgAccept();
	dlgStretch(1);
  }
};

}
