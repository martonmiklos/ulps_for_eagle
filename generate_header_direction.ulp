/*
	Copyright 2013, 2014  Miklos Marton <martonmiklosqdev [at] gmail [pont] com>
	ULP to generate macros from net definitions for AVR GCC or PIC XC projects.
	
	Generates macros for accessing the pin's direction, read, write registers more human friendly way.
	For e.g. if you have a net named relay_drive_0 in your schematic this ULP will define relay_drive_0_PIN 
	relay_drive_0_DDR on AVR platform. 
	
	The ULP also checks the nets connected to the selected device's pins and tries to determine the pins direction
	to generate default values for the data directions registers.
	
	The data direction calculation policy is the follwing:
	- By default every bit is set to output. 
	- For ports where nothing is connected no default value will be generated.
	- For ports where any of the pins are conneted to a net the direction will be set to input
	- If one of the follwing pin types are connected the pin will be set to input:
		- OUT
		- OC
		- SUP

	Usage with AVR-gcc details: http://users.atw.hu/balubati/blog/index.php?entry=entry130824-101447
	
	This program is free software: you can redistribute it and/or modify
    it under the terms of the GNU General Public License as published by
    the Free Software Foundation, either version 3 of the License, or
    (at your option) any later version.

    This program is distributed in the hope that it will be useful,
    but WITHOUT ANY WARRANTY; without even the implied warranty of
    MERCHANTABILITY or FITNESS FOR A PARTICULAR PURPOSE.  See the
    GNU General Public License for more details.

    You should have received a copy of the GNU General Public License
    along with this program.  If not, see <http://www.gnu.org/licenses/>.
*/


#usage "<b>ULP to generate macros from net definitions for AVR GCC or PIC XC projects.</b>\n"
       "<P>RUN generate_header.ulp <AVR/PIC> <RefDes> <FileName></P>"
       "<UL>"
       "<LI><B>AVR/PIC:</B> specify the target header file type</LI>"
	   "<LI><B>RefDes:</B> RefDes of the selected MCU</LI>"
       "<LI><B>Filename:</B> filename of output file (hwconfig.h in the currently opened project will be used if left out)</LI>"
       "</UL>"
       "<p>"
       "Generates a list of all nets in the specified list (see ClassNames above), with one net per line in the output file. Nets are"
       " sorted alphabetically.</P>"
       "<p>"
       "<author>Author: Miklos Marton (martonmiklosqdev -at- gmail.com)</author>"

/*
EAGLE UL_PIN.direction values:
0 PIN_DIRECTION_NC not connected
1 PIN_DIRECTION_IN input
2 PIN_DIRECTION_OUT output (totem-pole)
3 PIN_DIRECTION_IO in/output (bidirectional)
4 PIN_DIRECTION_OC open collector
5 PIN_DIRECTION_PWR power input pin
6 PIN_DIRECTION_PAS passive
7 PIN_DIRECTION_HIZ high impedance output
8 PIN_DIRECTION_SUP supply pin
*/

enum {
	AVR_libc = 0,
	PIC_XC = 1
};

string directionLUT[] = {
	"NC",
	"IN",
	"OU",
	"IN",
	"OC",
	"PWR",
	"PAS",
	"HIZ",
	"SUP"
};

enum {
	DirectionOutput = 0,
	DirectionInput
};

// an enum for the all bits input values
enum {
	DirectionDefaultAVR = 0, 
	DirectionDefaultPIC = 255
};

void ErrorMessage(string message) 
{
    string s;
    sprintf(s,":%s",message);
    dlgMessageBox(s);
    exit(1);
}


int outputType = AVR_libc;
string filePath = "hwconfig.h";
string mcuRefDes = "IC1";

string partNames[];
int i = 0;
schematic(SCH) {
	SCH.parts(PART) {
		// list only devices with 8 pin or more
		int pinCount = 0;
		PART.instances(INST) {
			INST.gate.symbol.pins(PIN) {
				pinCount++;
			}
		}
		
		if (pinCount >= 8) {
			partNames[i] = PART.name;
			i++;
		}
	}
}

if (argc < 2) {
	dlgDialog("Choose the part") {
		dlgComboBox(partNames, i);
		dlgGroup("Generate for:") {
			dlgRadioButton("&AVR (avr-libc headers)", outputType);
			dlgRadioButton("&Microchip PIC (C18/XC)", outputType);
		}
		
		dlgHBoxLayout {
			dlgLabel("Output file:");
			dlgStringEdit(filePath);
		} 
		dlgPushButton("Generate header") dlgAccept();
	};
	mcuRefDes = partNames[i];
} else {
	if (argv[1] == "AVR") {
		outputType = AVR_libc;
	} else if (argv[1] == "PIC") {
		outputType = PIC_XC;
	} else {
	    string s;
		sprintf(s,"Unknown device type: %s (available options AVR or PIC)", argv[1]);
		dlgMessageBox(s);
		exit(1);
	}
	mcuRefDes = argv[2];
	filePath = argv[3];
}


/**
 * str_replace
 *
 * Replaces all occurrences of a substring found within a string.
 */
string str_replace(string search, string replace, string subject) {
    int lastpos = 0;
    while(strstr(subject, search, lastpos) >= 0) {
        int pos = strstr(subject, search, lastpos);
        string before = strsub(subject, 0, pos);
        string after = strsub(subject, pos + strlen(search));
        subject = before + replace + after;
        lastpos = pos + strlen(replace);
    }
    return subject;
}



output(filePath, "wt") {
	string filePathParts[];
	strsplit(filePathParts, filename(filePath), '.');
	string fileBaseName = filePathParts[0];
	printf("#ifndef %s_H\n", strupr(fileBaseName));
	printf("#define %s_H\n\n", strupr(fileBaseName));
	printf("//-----------------------------------------------------------------\n");
	printf("//------------------------- DO NOT MODIFY -------------------------\n");
	printf("//------------------Generated with the generate_hearer.ulp---------\n");
	printf("//-----------------------------------------------------------------\n\n\n");
	
	string currentPinName = "";
	int currentPinDirection = DirectionOutput;
	int len = 0;
	// EAGLE ULPs does not supports associative arrays.
	// this array will be used to hold the data directions DDRA -> portDirections[0] DDRZ -> portDirections[25]
	int portDirections[];
	
	// fill the portDirections array with -1 to mark all unused
	for (int i = 0; i<26; i++)
		portDirections[i] = -1;
	
	schematic(SCH) {
		string regexp; 
		char defaultPortDirection;
		if (outputType == PIC_XC) {
			regexp = "R([A-Z])([0-7])(.*)"; // PIC libraries usually names the pins as RD7 style (PORTD7)
			defaultPortDirection = DirectionDefaultPIC; 
			printf("#include <xc.h>\n\n");
		} else if (outputType == AVR_libc) {
			regexp = "P([A-Z])([0-7])(.*)"; // AVR libraries usually names the pins as PD7 style (PORTD7)
			defaultPortDirection = DirectionDefaultAVR; 
		}
		
		SCH.nets(N) { // loop through all nets
			N.pinrefs(P) { // loop through all pinrefs connected to the current net
				if (P.instance.name == mcuRefDes) { // if this pinref is belongs to our device
					int matchPosition = strxstr(P.pin.name, regexp, 0);
					if (matchPosition != -1) { // check that this pin belongs to a port (not VCC, GND, OSC/whatever else)
						string subString = strsub(P.pin.name, matchPosition+1, 1); // extract the port letter (D in the case of RD7 or PD7)
						char portLetter = subString[0];
						
						/* if there were not any nets connected to the current port 
						 * parsed previously mark it as used by setting it to default port direction (all input) */
						if (portDirections[portLetter-'A'] == -1)
							portDirections[portLetter-'A'] = defaultPortDirection;						
						
						subString = strsub(P.pin.name, matchPosition+2, 1);
						char pinNumber = subString[0];
						string netName = N.name;
						// replace the ! symbol in the negated netnames since the c compiler does not allows to use it in a constant name
						if (strchr(netName, '!') == 0) {  
							sprintf(netName, "n%s", strsub(netName, 1));
						}
						
						netName = str_replace("/", "_", netName);
						
						if (outputType == AVR_libc) {
							printf("#define %s_PORT   PORT%c\n", netName, portLetter);
							printf("#define %s_PINREG PIN%c\n", netName, portLetter);
							printf("#define %s_PIN    %c\n", netName, pinNumber);
							printf("#define %s_DDR    DDR%c\n", netName, portLetter);
							printf("#define %s        %c,%c\n\n", netName, portLetter, pinNumber);
						} else if (outputType == PIC_XC) {
							// replace the ! symbol in the negated netnames since the c compiler does not allows to use it in a constant name
							if (strchr(netName, '!') == 0) {  
								sprintf(netName, "n%s", strsub(netName, 1));
							}
							
							printf("#define %s_LAT   LAT%c\n", netName, portLetter);
							printf("#define %s_PORT   PORT%c\n", netName, portLetter);
							printf("#define %s_TRISREG TRIS%c\n", netName, portLetter);
							printf("#define %s        PORT%cbits.R%c%c\n", netName, portLetter, portLetter, pinNumber);
							printf("#define %s_bit    %c\n\n", netName, pinNumber);
						}
						
						// assume that the pin is output
						currentPinDirection = DirectionOutput;
						currentPinName = P.pin.name;
						SCH.nets(N2) {
							if (N2.name == N.name) {
								N2.pinrefs(P2) {
									/* set to input if there is an another pin connected to the current net and has the follwing directions:
									 * - OUT
									 * - OC
									 * - SUP
									 */
									if (P2.instance.name != mcuRefDes) {
										if (P2.pin.direction == PIN_DIRECTION_OUT ||
											P2.pin.direction == PIN_DIRECTION_SUP ||
											P2.pin.direction == PIN_DIRECTION_OC) {
											currentPinDirection = DirectionInput;
										}
									}
								}
							}
						}
						
						pinNumber -= '0'; // the pinNumber below will be used as a bitmask index (0-7)
						if (outputType == PIC_XC && currentPinDirection==DirectionOutput) { 
							portDirections[int(portLetter-'A')] &= ~(1<<pinNumber);// at PIC micros output is set to 0
						} else if (outputType == AVR_libc && currentPinDirection==DirectionOutput) {
							portDirections[int(portLetter-'A')] |= (1<<pinNumber);// AVR micros output is set to 1
						}
					}
				}
			}
		}
		
		printf("//-----------------------------------------------------------------\n");
		printf("//-- The default port direction values are depending on the -------\n");
		printf("//-- connected devices pin's directions. Always double check ------\n");
		printf("//-- the values here if you do not want frontdrive two outputs! ---\n");
		printf("//-----------------------------------------------------------------\n\n");
		for (int i = 0; i<26; i++) {
			if (portDirections[i] != -1) {
				if (outputType == PIC_XC)
					printf("#define TRIS%c_default_value 0x%02X;\n", char(i+'A'), char(portDirections[i]));
				else 
					printf("#define DDR%c_default_value 0x%02X;\n", char(i+'A'), char(portDirections[i]));
			}
		}
		
		printf("\n#endif //#define %s_H", strupr(fileBaseName));
	}
}
