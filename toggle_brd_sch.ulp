#usage "en: <b>An ULP to switch between the board and the schematic</b>"
            "<p>"
            "Assign the 'RUN toggle_brd_sch;' command to a shortcut (I prefer Ctrl+E to get similar behaviour to NI LabVIEW)"
            "<p>"
			"<p>The latest version can be obtained from the <a href=https://github.com/martonmiklos/ulps_for_eagle>GitHub</a></p>"
			"<p><author>Author: <a href=mailto:martonmiklosqdev@gmail_dot_com>Miklos Marton </author></a><p>"
string ret = "";
if (board) {
    sprintf(ret, "EDIT .sch");
    exit(ret);
} else if (schematic) {
    sprintf(ret, "EDIT .brd");
    exit(ret);
}

exit(0);
