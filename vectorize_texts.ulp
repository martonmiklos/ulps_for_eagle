string ret = "GRID MIC 1;\n";
string cmd = ""; 
schematic(SCH) {
	SCH.sheets(SH) {
		sprintf(cmd, "EDIT .s%d;\n", SH.number);
		ret += cmd;
		SH.instances(I) {
			I.texts(text) {
				sprintf(cmd, "CHANGE FONT VECTOR (%f %f);\n", u2mic(text.x), u2mic(text.y));
				ret += cmd;
				sprintf(cmd, "CHANGE SIZE 0.05inch (%f %f);\n", u2mic(text.x), u2mic(text.y));
				ret += cmd;
			}
		}
	}
	
	string unit = "";
	switch (SCH.grid.unit) {
	case GRID_UNIT_MIC: unit = "microns"; break;
	case GRID_UNIT_MM : unit = "millimeter"; break;
	case GRID_UNIT_MIL: unit = "mil"; break;
	case GRID_UNIT_INCH: unit = "inch"; break;
	}
	sprintf(cmd, "GRID %s %f;\n", unit, SCH.grid.distance);
	ret += cmd;
}
exit(ret);
