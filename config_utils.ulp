int cfgget_int(string key, int defaultValue)
{
    string tmp;
    sprintf(key, "%s.%s", ULP_KEY, key);
    sprintf(tmp, "%d", defaultValue);
    return strtol(cfgget(key, tmp));
}

real cfgget_real(string key, real defaultValue)
{
    string tmp;
    sprintf(key, "%s.%s", ULP_KEY, key);
    sprintf(tmp, "%f", defaultValue);
    return strtod(cfgget(key, tmp));
}

void cfgset_int(string key, int value)
{
    string tmp;
    sprintf(key, "%s.%s", ULP_KEY, key);
    sprintf(tmp, "%d", value);
    cfgset(key, tmp);
}

void cfgset_real(string key, real value)
{
    string tmp;
    sprintf(key, "%s.%s", ULP_KEY, key);
    sprintf(tmp, "%f", value);
    cfgset(key, tmp);
}

string cfgget_string(string key, string defaultValue)
{
    string tmp;
    sprintf(key, "%s.%s", ULP_KEY, key);
    sprintf(tmp, "%s", defaultValue);
    return cfgget(key, tmp);
}

void cfgset_string(string key, string value)
{
    string tmp;
    sprintf(key, "%s.%s", ULP_KEY, key);
    sprintf(tmp, "%s", value);
    cfgset(key, tmp);
}
