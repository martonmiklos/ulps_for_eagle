#require 7.0

#usage  "en:  <h3>Highlights parts with a given value.</h3>\n"
             "This ULPs works from within a board or a schematic.<br>"
			 "This ULP works with Eagle 7 (tested with 7.5.0). Eagle 6 not tested!<br>"
			 "Modified Version of Rene König<br>"
             "<p><author>Author: Karsten Brandt</author>",
        "de:  <h3>Hebt Parts mit einem gegebenen Value hervor.</h3>\n"
             "Dieses ULP arbeitet aus Boards oder Schematics heraus.<br>"
			 "Diese ULP funktioniert mit Eagle 7 (getested mit 7.5.0<). Nicht getested mit Eagle 6!<br>"
			 "Modifizierte Version von Rene König<br>"
             "<p><author>Autor: Karsten Brandt</author>"

#include "useful-routines.ulp"
#include "IniFile.ulp"

enum { ShowTopOnly, ShowBothSides, ShowBottomOnly };

string strTexts[] =
{
    "en\v"
    "de\v"
    ,
    ";This ULP requires a board or a schematic. Funktionier mit Eagle 7 (getested mit 7.5.0). Nicht getested mit Eagle 6!\v"
    ";Dieses Ulp funktioniert nur in Boards und Schematics. Works with Eagle 7 (tested with 7.5.0). Not tested with Eagle 6!\v"
    ,
    "Please type in the value you want to highlight.\v"
    "Geben Sie den hervorzuhebenden Value ein.\v"
    ,
    ";No elements found with value \"%s\".\v"
    ";Es wurden keine Elemente mit dem Value \"%s\" gefunden.\v"
};

string strMessage;
string strScript;
int nCount;
int showPartsOnSides = ShowBothSides;

string Translate(string src)
{
    string strLoc = lookup(strTexts, src, strstr(strTexts[0], language()) / 3, '\v');
    return((strLoc != "") ? strLoc : src);
}

string GetIniFileName(void)
{
    return filesetext(argv[0], ".ini");
}

string GetScriptName(void)
{
    return filesetext(argv[0], ".scr");
}

string InputBox(string strPrompt, string strTitle, string strDefault)
{
    string strReturn = strDefault;
    int nResult = dlgDialog(strTitle)
    {
        dlgGridLayout
        {
            dlgCell(0, 0)
            {
                dlgHBoxLayout
                {
                    dlgLabel(strPrompt);
                    dlgSpacing(20);

                    dlgGroup("Show on side(s):") {
                        dlgRadioButton("&Top", showPartsOnSides);
                        dlgRadioButton("&Both", showPartsOnSides);
                        dlgRadioButton("&Bottom", showPartsOnSides);
                    } 
                    
                    dlgVBoxLayout
                    {
                        dlgPushButton("+OK") dlgAccept();
                        dlgPushButton("Cancel") dlgReject();
                    }
                }
            }
            
            dlgCell(1, 0)
            {
                dlgStringEdit(strReturn);
            }
        }
    };

    return((nResult > 0) ? strReturn : "");
}

int found_bit=0;
if(board) board(B)
{
    showPartsOnSides = INI_GetInteger(strlwr(get_ulp_name()), B.name + "_side", ShowBothSides, GetIniFileName());
    if (showPartsOnSides > ShowBottomOnly)
        showPartsOnSides = ShowBothSides;
  
    string strValue = "";
    if (argc == 1) {
        // No command line arguments, start the GUI
        strValue = InputBox(Translate("Please type in the value you want to highlight."), get_ulp_name(), INI_GetString(strlwr(get_ulp_name()), B.name + "_value", "", GetIniFileName()));
    } else {
        // command line arguments are handled in the following way:
        // first argument: part value, 
        // second (optional): side name {top,bottom}
        if (argc == 2) {
            strValue = argv[1];
        } else if (argc == 3) {
            strValue = argv[1];
            showPartsOnSides = ShowBothSides;
            if (strlwr(argv[2]) == "top") {
                showPartsOnSides = ShowTopOnly;
            } else if (strlwr(argv[2]) == "bottom") {
                showPartsOnSides = ShowBottomOnly;
            }
        }
    }

    
    if(strValue == "")
        exit(EXIT_SUCCESS);

    INI_PutString(strlwr(get_ulp_name()), B.name + "_value", strValue, GetIniFileName());
    INI_PutInteger(strlwr(get_ulp_name()), B.name + "_side", showPartsOnSides, GetIniFileName());
    strScript = GetScriptName();
    
    output(strScript)
    {
        printf("#\n");
        //printf("window;\n\n");

        B.elements(E)
        {
            if (showPartsOnSides != ShowBothSides) {
                if (showPartsOnSides == ShowTopOnly && E.mirror != 0)
                    continue;
                
                if (showPartsOnSides == ShowBottomOnly && E.mirror == 0)
                    continue;
            }
            
            if((strlwr(E.value) == strlwr(strValue)) && (found_bit==0))
            {
                //printf("show %s\n", E.name);
				printf("show %s ", E.name);
				found_bit=1;
                ++nCount;
            }
			else if((strlwr(E.value) == strlwr(strValue)) && (found_bit==1))
			{
				printf(" %s ", E.name);
                ++nCount;
			}
        }
		
        //printf("\n;\n");
		printf("\nwindow\n\n");
    }

    if(!nCount)
    {
        sprintf(strMessage, Translate(";No elements found with value \"%s\"."), strValue);
        dlgMessageBox(strMessage);
        exit(EXIT_FAILURE);
    }
    else
    {
        exit("script " + "'"+strScript+"'" + ";");
    }
}
else if(sheet) sheet(S)
{
    string strName;

    schematic(SCH)
    {
        strName = SCH.name;
    }

    string strValue = InputBox(Translate("Please type in the value you want to highlight."), get_ulp_name(), INI_GetString(strlwr(get_ulp_name()), strName, "", GetIniFileName()));

    if(strValue == "")
        exit(EXIT_SUCCESS);

    INI_PutString(strlwr(get_ulp_name()), strName, strValue, GetIniFileName());
    strScript = GetScriptName();

    output(strScript)
    {
        printf("#\n");
        //printf("window;\n\n");

        S.parts(P)
        {
            if((strlwr(P.value) == strlwr(strValue)) && (found_bit==0))
            {
                printf("show %s ", P.name);
				found_bit=1;
                ++nCount;
            }
			else if((strlwr(P.value) == strlwr(strValue)) && (found_bit==1))
            {
                printf(" %s ", P.name);
                ++nCount;
            }
        }

        //printf("\n;\n");
		printf("\nwindow\n\n");
    }

    if(!nCount)
    {
        sprintf(strMessage, Translate(";No elements found with value \"%s\"."), strValue);
        dlgMessageBox(strMessage);
        exit(EXIT_FAILURE);
    }
    else
    {
        exit("script " + "'"+strScript+"'" + ";");
    }
}
else
{
    dlgMessageBox(Translate(";This ULP requires a board or a schematic."));
}
