#usage "<b>Normalize silkscreen text sizes</b><HR>\n"
       "<p>This ULP program smashes all texts on the silkscreen layers. It then normalizes the "
       "texts so that they all have the same size and thickness. Ratio is calculated from "
       "the desired thickness.</p>"
       "<author>Author: Tennessee Carmel-Veilleux (veilleux@ameth.org)</author>"

/****************************************************************************************
*                                                                                       *
*   Normalize silkscreen text sizes                                                     *
*                                                                                       *
*   Filename: normalize-text.ulp                                                        *
*   Version: 1.0                                                                        *
*   Author: Tennessee Carmel-Veilleux <veilleux@ameth.org>                             *
*   Date: March 31st 2005                                                               *
*   Company: Entreprises Ten Tech                                                       *
*                                                                                       *                                                                                       *
*   This ULP program smashes all texts on the silkscreen layers. It then normalizes the *
*   texts so that they all have the same size and thickness. Ratio is calculated from   *
*   the desired thickness.                                                              *
*                                                                                       *
****************************************************************************************/

string ULP_KEY = "NormalizeText";

#require 5.0300;
#include "config_utils.ulp"

string VERSION = "1.4";  // 2018-11-03 martonmiklosqdev@gmail.com

enum {UNIT_MIL, UNIT_MM, UNIT_PERCENTAGE, UNIT_INVALID};

int  textSizeUnit;
real textSize;

real textThickness;
int  textThicknessUnit;

int text_ratio; // Calculated text ratio

enum {LEAVE_FONT_AS_IS, SET_VECTOR_FONT, SET_PROPORTIONAL_FONT, SET_FIXED_FONT};
string fontTypeOptions[] = { "Leave as is", "Vector", "Proportional", "Fixed" };
int selectedFontType;

string textSizeUnitOptions[] = {"mil", "mm"};
string textThicknessUnitOptions[] = {"mil", "mm", "%"};


int silk_screen_layers[] = {
    // schematic layers
    LAYER_NAMES,
    LAYER_VALUES,
    // board layers
    LAYER_TPLACE, 
    LAYER_BPLACE, 
    LAYER_TNAMES,
    LAYER_BNAMES, 
    LAYER_TVALUES, 
    LAYER_BVALUES,
    LAYER_TDOCU, 
    LAYER_BDOCU, 
    // 2008-11-07 Layer 125, 126 is created by panalize.ulp.
    125, 
    126
};

int actualvisible = 0;

int process_tPlace = cfgget_int("process_tPlace", 1);
int process_bPlace = cfgget_int("process_tPlace", 1);
int process_tNames = cfgget_int("process_tNames", 1);
int process_bNames = cfgget_int("process_bNames", 1);
int process_tValues = cfgget_int("process_tValues", 1);
int process_bValues = cfgget_int("process_bValues", 1);
int process_tDocu = cfgget_int("process_tDocu", 1);
int process_bDocu = cfgget_int("process_bDocu", 1);
int process_tNames_panelize = cfgget_int("process_tNames_panelize", 1);
int process_bNames_panelize = cfgget_int("process_bNames_panelize", 1);
int process_Names = cfgget_int("process_Names", 1);
int process_Values = cfgget_int("process_Values", 1);
int process_NonXREFLabels = cfgget_int("process_NonXREFLabels", 1);
int process_XREFLabels = cfgget_int("process_XREFLabels", 1);

int result = 0; // Dialog result

void saveSchConfig() 
{
    cfgset_real("sch_textSize", textSize);
    cfgset_int("sch_textSizeUnit", textSizeUnit);
    
    cfgset_real("sch_textThickness", textThickness);
    cfgset_int("sch_textThicknessUnit", textThicknessUnit);
    
    cfgset_int("sch_selectedFontType", selectedFontType);
    
    cfgset_int("process_Names", process_Names);
    cfgset_int("process_Values", process_Values);
    cfgset_int("process_NonXREFLabels", process_NonXREFLabels);
    cfgset_int("process_XREFLabels", process_XREFLabels);
}

void saveBrdConfig()
{
    cfgset_real("textSize", textSize);
    cfgset_int("textSizeUnit", textSizeUnit);
    
    cfgset_real("textThickness", textThickness);
    cfgset_int("textThicknessUnit", textThicknessUnit);
    
    cfgset_int("selectedFontType", selectedFontType);
    cfgset_int("process_tPlace", process_tPlace);
    cfgset_int("process_bPlace", process_bPlace);
    cfgset_int("process_tNames", process_tNames);
    cfgset_int("process_bNames", process_bNames);
    cfgset_int("process_tValues", process_tValues);
    cfgset_int("process_bValues", process_bValues);
    cfgset_int("process_tDocu", process_tDocu);
    cfgset_int("process_bDocu", process_bDocu);
    cfgset_int("process_tNames_panelize", process_tNames_panelize);
    cfgset_int("process_bNames_panelize", process_bNames_panelize);
}

string str; // Temporary string
string cmd = "SET UNDO_LOG OFF;\n"; // Script command to execute
/* ------------- UTILITY FUNCTIONS --------------- */

//
// Redisplays the layers that were visible when the ULP was started
//
void ResetVisibleBrd(UL_BOARD B) 
{
    sprintf(str, "DISP NONE;\nDISP ");
    cmd += str;
    B.layers(L) {
        if (L.visible) {
            sprintf(str, "%d ", L.number);
            cmd += str;
        }
    }
    cmd += ";\n";
}

void ResetVisibleSch(UL_SCHEMATIC S) 
{
    sprintf(str, "DISP NONE;\nDISP ");
    cmd += str;
    S.layers(L) {
        if (L.visible) {
            sprintf(str, "%d ", L.number);
            cmd += str;
        }
    }
    cmd += ";\n";
}



//
// Returns 1 if the layer is selected
//
int layerEnabled(int layer) 
{
    int i = 0;
    int found = 0;
    
    switch (layer) {
    case LAYER_TPLACE: if (!process_tPlace) return 0; break;
    case LAYER_BPLACE: if (!process_bPlace) return 0; break;
    case LAYER_TNAMES: if (!process_tNames) return 0; break;
    case LAYER_BNAMES: if (!process_bNames) return 0; break;
    case LAYER_TVALUES: if (!process_tValues) return 0; break;
    case LAYER_BVALUES: if (!process_bValues) return 0; break;
    case LAYER_TDOCU: if (!process_tDocu) return 0; break;
    case LAYER_BDOCU: if (!process_bDocu) return 0; break;
    case 125: if (!process_tNames_panelize) return 0; break;
    case 126: if (!process_bNames_panelize) return 0; break;
    case LAYER_NAMES: if (!process_Names) return 0; break;
    case LAYER_VALUES: if (!process_Values) return 0; break;
    }
    
    do {    // 2008-11-07
      if (layer == silk_screen_layers[i]) {
        found = 1;
        if (actualvisible != layer) { // display only the layer with text to change
                                      // in a script can not select texts by thew same coodiante
          sprintf(str, "DISPLAY NONE %d;\n", layer);
          cmd += str;
        }
        break;
      }
      i++;
    } while(silk_screen_layers[i]);

    return found;
}

//
// Resizes a text element to the specified size and ratio
//
void ProcessText(UL_TEXT T, real size, int ratio, int action) 
{
    if (layerEnabled(T.layer)) {
        switch (textSizeUnit) {
        case UNIT_MIL:
            sprintf(str,"CHANGE SIZE %.4fmil (%.4fmil %.4fmil);\nCHANGE RATIO %d (%.4fmil %.4fmil);\n",
                    size, u2mil(T.x), u2mil(T.y), ratio, u2mil(T.x), u2mil(T.y));
            break;
        case UNIT_MM:
            sprintf(str,"CHANGE SIZE %.4fmm (%.4fmm %.4fmm);\nCHANGE RATIO %d (%.4fmm %.4fmm);\n",
                    size, u2mm(T.x), u2mm(T.y), ratio, u2mm(T.x), u2mm(T.y));
            break;
        }
        cmd += str;
        
        string font = "";
        switch (action) {
        case LEAVE_FONT_AS_IS:
            return;
        case SET_FIXED_FONT:
            font = "FIXED";
            break;
        case SET_PROPORTIONAL_FONT:
            font = "PROPORTIONAL ";
            break;
        case SET_VECTOR_FONT:
            font = "VECTOR";
            break;
        }
        switch (textSizeUnit) {
            case UNIT_MIL:
                sprintf(str,"CHANGE FONT %s (%.4fmil %.4fmil);\n",
                        font, u2mil(T.x), u2mil(T.y));
                break;
            case UNIT_MM:
                sprintf(str,"CHANGE FONT %s (%.4fmm %.4fmm);\n",
                        font, u2mm(T.x), u2mm(T.y));
                break;
        }
        cmd += str;
    }
}

//
// Smashes all parts that have an associated package on the board and resize
// all text to SIZE and RATIO.
//
void ProcessBrdTexts(real size, int ratio, int fontType) {
    // Display the origins of components
    switch (textSizeUnit) {
        case UNIT_MIL:
            sprintf(str,"GRID MIL 1;\n");
            break;
        case UNIT_MM:
            sprintf(str,"GRID MM 0.1;\n");
            break;
    }
    cmd += str;

    cmd += "DISPLAY NONE 23 24;\n";

    board(B) {
        B.elements(E) {
            if (E.package) {
                if (!E.smashed) {
                    // do not resmash the part since 9.2 the smash of the smashed part will reposition the text
                    sprintf(str,"SMASH %s;\n", E.name);
                    cmd += str;
                }
                // Change smashed texts
                E.texts(T) {
                    ProcessText(T, size, ratio, fontType);
                }

                // Change unsmashed texts
                E.package.texts(T) {
                    ProcessText(T, size, ratio, fontType);
                }
            }
        }

        // Change all manually-added texts
        B.texts(T) {
            ProcessText(T, size, ratio, fontType);
        }

        ResetVisibleBrd(B);
    }
    cmd += "SET UNDO_LOG ON;\nGRID LAST;\n";
}

//
// Smashes all parts that have an associated package on the board and resize
// all text to SIZE and RATIO.
//
void ProcessSchTexts(real size, int ratio, int fontType) 
{
    // Display the origins of components
    switch (textSizeUnit) {
        case UNIT_MIL:
            sprintf(str,"GRID MIL 1;\n");
            break;
        case UNIT_MM:
            sprintf(str,"GRID MM 0.1;\n");
            break;
    }
    cmd += str;
    
    schematic(SCH) {
        SCH.sheets(S) {
            sprintf(cmd, "%s\nEDIT .s%d;\n", cmd, S.number);
            cmd += str;
            cmd += "WINDOW FIT;\n";
            S.instances(E) {
                if (!E.smashed) {
                    // do not resmash the part since 9.2 the smash of the smashed part will reposition the text
                    sprintf(str,"SMASH %s;\n", E.name);
                    cmd += str;
                }
                E.texts(T) {
                    ProcessText(T, size, ratio, fontType);
                }
                
                E.gate.symbol.texts(T) {
                    ProcessText(T, size, ratio, fontType);
                }
            }
            
            // Change all manually-added texts to the selected layers
            S.texts(T) {
                ProcessText(T, size, ratio, fontType);
            }
            
            if (process_NonXREFLabels || process_XREFLabels) {
                S.nets(N) {
                    N.segments(SEG) {
                        SEG.labels(label) {
                            if ((process_NonXREFLabels && label.xref == 0) ||
                                  process_XREFLabels && label.xref == 1) {
                                ProcessText(label.text, size, ratio, fontType);
                            }
                        }
                    }
                }
            }
        }
        ResetVisibleSch(SCH);
        string unit = "";
        switch (SCH.grid.unit) {
        case GRID_UNIT_MIC: unit = "microns"; break;
        case GRID_UNIT_MM : unit = "millimeter"; break;
        case GRID_UNIT_MIL: unit = "mil"; break;
        case GRID_UNIT_INCH: unit = "inch"; break;
        }
        sprintf(str, "GRID %s %f;\n", unit, SCH.grid.distance);
        cmd += str;
    }
    cmd += "SET UNDO_LOG ON;\n";
}

//output("/tmp/foo.txt", "wt") {
/* ------------- MAIN ROUTINE --------------- */
if (board) {
    int visibleLayers[];
    int textSizeInU, textThicknessInU;
    
    textSize = cfgget_real("textSize", 1.0);
    
    textSizeUnit = cfgget_int("textSizeUnit", UNIT_MM);
    if (textSizeUnit > UNIT_MM)
        textSizeUnit = UNIT_MIL;
    int lastTextSizeUnit = textSizeUnit;
    
    textThickness = cfgget_real("textThickness", 0.1);
    textThicknessUnit = cfgget_int("textThicknessUnit", UNIT_PERCENTAGE);
    if (textThicknessUnit > UNIT_PERCENTAGE)
        textThicknessUnit = UNIT_PERCENTAGE;
    int  lastTextThicknessUnit = textThicknessUnit;

    switch (textSizeUnit) {
    case UNIT_MIL:
        textSizeInU = mil2u(textSize);
        break;
    case UNIT_MM:
        textSizeInU = mm2u(textSize);
        break;
    }
    
    switch (textThicknessUnit) {
    case UNIT_MIL:
        textThicknessInU = mil2u(textThickness);
        break;
    case UNIT_MM:
        textThicknessInU = mm2u(textThickness);
        break;
    case UNIT_PERCENTAGE:
        switch (textSizeUnit) {
        case UNIT_MIL:
            textThicknessInU = textThickness * mil2u(textSize);
            break;
        case UNIT_MM:
            textThicknessInU = textThickness * mm2u(textSize);
            break;
        }
        break;
    }
    
    selectedFontType = cfgget_int("selectedFontType", LEAVE_FONT_AS_IS);
    if (selectedFontType > SET_FIXED_FONT)
        selectedFontType = LEAVE_FONT_AS_IS;
    
    result = dlgDialog("Normalize text sizes") {
        sprintf(str,"<qt><H3><P>Normalize silkscreen text sizes %s</P></H3>"+
                    "<P><B>By Tennessee Carmel-Veilleux (veilleux@ameth.org)</B></P>"+
                    "<HR><P>This ULP normalizes all the text on the silkscreen layers to "+
                    "the specified size and thickness. The ratio is automatically calculated " +
                    "from the size and thickness.</P></qt>", VERSION);
        dlgLabel(str);
        dlgTabWidget {
            dlgTabPage("Options") {
                // Options
                dlgHBoxLayout {
                    dlgSpacing(20);
                    dlgGridLayout {
                        dlgCell(0,0) dlgLabel("Text size:");
                        dlgCell(0,1) dlgRealEdit(textSize, 0, 2000.0)
                        dlgCell(0,2) dlgComboBox(textSizeUnitOptions, textSizeUnit) {
                            if (lastTextSizeUnit != textSizeUnit) {
                                switch (lastTextSizeUnit) {
                                case UNIT_MIL:
                                    textSizeInU = mil2u(textSize);
                                    break;
                                case UNIT_MM:
                                    textSizeInU = mm2u(textSize);
                                    break;
                                }
                                
                                switch (textSizeUnit) {
                                case UNIT_MIL:
                                    textSize = u2mil(textSizeInU);
                                    break;
                                case UNIT_MM:
                                    textSize = u2mm(textSizeInU);
                                    break;
                                }
                                lastTextSizeUnit = textSizeUnit;
                            }
                        }

                        dlgCell(1,0) dlgLabel("Text Thickness:");
                        dlgCell(1,1) dlgRealEdit(textThickness, 0, 500.0);
                        dlgCell(1,2) dlgComboBox(textThicknessUnitOptions, textThicknessUnit) {
                            if (lastTextThicknessUnit != textThicknessUnit) {
                                switch (lastTextThicknessUnit) {
                                case UNIT_MIL:
                                    textThicknessInU = mil2u(textThickness);
                                    break;
                                case UNIT_MM:
                                    textThicknessInU = mm2u(textThickness);
                                    break;
                                case UNIT_PERCENTAGE:
                                    switch (textSizeUnit) {
                                    case UNIT_MIL:
                                        textThicknessInU = textThickness * mil2u(textSize);
                                        break;
                                    case UNIT_MM:
                                        textThicknessInU = textThickness * mm2u(textSize);
                                        break;
                                    }
                                    break;
                                }
                                
                                switch (textThicknessUnit) {
                                case UNIT_MIL:
                                    textThickness = u2mil(textThicknessInU);
                                    break;
                                case UNIT_MM:
                                    textThickness = u2mm(textThicknessInU);
                                    break;
                                case UNIT_PERCENTAGE:
                                    textThickness = (textThicknessInU / textSizeInU) * 100.0;
                                    break;
                                }
                                lastTextThicknessUnit = textThicknessUnit;
                            }
                        }
                        
                        dlgCell(2,0) dlgLabel("Text type:");
                        dlgCell(2,1) dlgComboBox(fontTypeOptions, selectedFontType);
                    }
                }
            }
            dlgTabPage("Layers") {
                dlgHBoxLayout {
                    dlgGridLayout {
                        dlgCell(0,0) dlgCheckBox("tPlace", process_tPlace);
                        dlgCell(1,0) dlgCheckBox("bPlace", process_bPlace);
                        dlgCell(2,0) dlgCheckBox("tNames", process_tNames);
                        dlgCell(3,0) dlgCheckBox("bNames", process_bNames);
                        dlgCell(4,0) dlgCheckBox("tValues", process_tValues);
                        dlgCell(5,0) dlgCheckBox("bValues", process_bValues);
                        
                        dlgCell(0,1) dlgCheckBox("tDocu", process_tDocu);
                        dlgCell(1,1) dlgCheckBox("bDocu", process_bDocu);
                        dlgCell(2,1) dlgCheckBox("tNames by panelize.ulp (125)", process_tNames_panelize);
                        dlgCell(3,1) dlgCheckBox("bNames by panelize.ulp (126)", process_bNames_panelize);
                    }
                }
            }
        }
        

        // Buttons
        dlgHBoxLayout {
            dlgStretch(1);
            dlgPushButton("+Normalize") dlgAccept();
            dlgPushButton("-Cancel") dlgReject();
        }
    };

    if (!result) {
        saveBrdConfig();
        exit(0);
    }

    if (textThicknessUnit == UNIT_PERCENTAGE) 
        text_ratio = textThickness;
    else
        text_ratio = int(round((textThickness / textSize) * 100.0)) + 1;

    if (text_ratio > 31) {
        text_ratio = 31;
        dlgMessageBox("!<qt><P><B>Ratio clipped to 31% !</B></P>"+
                      "<P>Make sure that text thickness is not too large for proper ratio.</P></qt>");
    }
    ProcessBrdTexts(textSize, text_ratio, selectedFontType);

    //  EditBox
    result = dlgDialog("Edit and execute script") {
        dlgHBoxLayout {
            dlgSpacing(500); // Force width of dialog to 500
        }
        dlgTextEdit(cmd);
        dlgHBoxLayout {
            dlgPushButton("+Execute") dlgAccept();
            dlgPushButton("-Cancel") dlgReject();
        }
    };

    // Execute script if it was accepted
    if (!result) {
        saveBrdConfig();
        exit(0);
    } else {
        saveBrdConfig();
        exit(cmd);
    }
} else if (schematic) {
    int textSizeInU, textThicknessInU;
    textSize = cfgget_real("sch_textSize", 70);
    
    textSizeUnit = cfgget_int("sch_textSizeUnit", UNIT_MIL);
    if (textSizeUnit > UNIT_MM)
        textSizeUnit = UNIT_MIL;
    int lastTextSizeUnit = textSizeUnit;
    
    textThickness = cfgget_real("sch_textThickness", 10);
    textThicknessUnit = cfgget_int("sch_textThicknessUnit", UNIT_PERCENTAGE);
    if (textThicknessUnit > UNIT_PERCENTAGE)
        textThicknessUnit = UNIT_PERCENTAGE;
    int  lastTextThicknessUnit = textThicknessUnit;

    switch (textSizeUnit) {
    case UNIT_MIL:
        textSizeInU = mil2u(textSize);
        break;
    case UNIT_MM:
        textSizeInU = mm2u(textSize);
        break;
    }

    selectedFontType = cfgget_int("sch_selectedFontType", LEAVE_FONT_AS_IS);
    if (selectedFontType > SET_FIXED_FONT)
        selectedFontType = LEAVE_FONT_AS_IS;
    
    result = dlgDialog("Normalize text sizes") {
        sprintf(str,"<qt><H3><P>Normalize schematic text sizes %s</P></H3>"+
                    "<P><B>By Miklos Marton (martonmiklosqdev@gmail.com)</B></P>"+
                    "<HR><P>This ULP normalizes all the text on the name/values layers to "+
                    "the specified size and thickness. The ratio is automatically calculated " +
                    "from the size and thickness.</P></qt>", VERSION);
        dlgLabel(str);

        dlgTabWidget {
            dlgTabPage("Options") {
                // Options
                dlgHBoxLayout {
                    dlgSpacing(20);
                    
                    dlgGridLayout {
                        dlgCell(0,0) dlgLabel("Text size:");
                        dlgCell(0,1) dlgRealEdit(textSize, 0, 2000);
                        dlgCell(0,2) dlgComboBox(textSizeUnitOptions, textSizeUnit) {
                            if (lastTextSizeUnit != textSizeUnit) {
                                switch (lastTextSizeUnit) {
                                case UNIT_MIL:
                                    textSizeInU = mil2u(textSize);
                                    break;
                                case UNIT_MM:
                                    textSizeInU = mm2u(textSize);
                                    break;
                                }
                                
                                switch (textSizeUnit) {
                                case UNIT_MIL:
                                    textSize = u2mil(textSizeInU);
                                    break;
                                case UNIT_MM:
                                    textSize = u2mm(textSizeInU);
                                    break;
                                }
                                lastTextSizeUnit = textSizeUnit;
                            }
                        }

                        dlgCell(1,0) dlgLabel("Text Thickness:");
                        dlgCell(1,1) dlgRealEdit(textThickness,0.0, 500.0);
                        dlgCell(1,2) dlgComboBox(textThicknessUnitOptions, textThicknessUnit) {
                            if (lastTextThicknessUnit != textThicknessUnit) {
                                switch (lastTextThicknessUnit) {
                                case UNIT_MIL:
                                    textThicknessInU = mil2u(textThickness);
                                    break;
                                case UNIT_MM:
                                    textThicknessInU = mm2u(textThickness);
                                    break;
                                case UNIT_PERCENTAGE:
                                    switch (textSizeUnit) {
                                    case UNIT_MIL:
                                        textThicknessInU = textThickness * mil2u(textSize);
                                        break;
                                    case UNIT_MM:
                                        textThicknessInU = textThickness * mm2u(textSize);
                                        break;
                                    }
                                    break;
                                }
                                
                                switch (textThicknessUnit) {
                                case UNIT_MIL:
                                    textThickness = u2mil(textThicknessInU);
                                    break;
                                case UNIT_MM:
                                    textThickness = u2mm(textThicknessInU);
                                    break;
                                case UNIT_PERCENTAGE:
                                    textThickness = (textThicknessInU / textSizeInU) * 100.0;
                                    break;
                                }
                                lastTextThicknessUnit = textThicknessUnit;
                            }
                        }
                        
                        dlgCell(2,0) dlgLabel("Text type:");
                        dlgCell(2,1) dlgComboBox(fontTypeOptions, selectedFontType);
                    }
                }
            }
            dlgTabPage("Layers") {
                dlgHBoxLayout {
                    dlgGridLayout {
                        dlgCell(0,0) dlgCheckBox("Part names", process_Names);
                        dlgCell(1,0) dlgCheckBox("Part values", process_Values);
                        dlgCell(2,0) dlgCheckBox("Non-XREF net labels", process_NonXREFLabels);
                        dlgCell(3,0) dlgCheckBox("XREF net labels", process_XREFLabels);
                    }
                }
            }
        }
        

        // Buttons
        dlgHBoxLayout {
            dlgStretch(1);
            dlgPushButton("+Normalize") dlgAccept();
            dlgPushButton("-Cancel") dlgReject();
        }
    };

    if (!result) {
        saveSchConfig();
        exit(0);
    }

    if (textThicknessUnit == UNIT_PERCENTAGE) 
        text_ratio = textThickness;
    else
        text_ratio = int(round((textThickness / textSize) * 100.0)) + 1;
    
    ProcessSchTexts(textSize, text_ratio, selectedFontType);

    //  EditBox
    result = dlgDialog("Edit and execute script") {
        dlgHBoxLayout {
            dlgSpacing(500); // Force width of dialog to 500
        }
        dlgTextEdit(cmd);
        dlgHBoxLayout {
            dlgPushButton("+Execute") dlgAccept();
            dlgPushButton("-Cancel") dlgReject();
        }
    };

    // Execute script if it was accepted
    if (!result) {
        saveSchConfig();
        exit(0);
    } else {
        saveSchConfig();
        exit(cmd);
    }
} else {
    dlgMessageBox(":You must run this ULP in a schematic or in a board !");
    exit(1);
}
//}
