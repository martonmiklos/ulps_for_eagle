#require 7.0

#usage  "en:  <h3>Highlights parts with a given value.</h3>\n"
             "This ULPs works from within a board or a schematic.<br>"
			 "This ULP works with Eagle 7 (tested with 7.5.0). Eagle 6 not tested!<br>"
			 "Modified Version of Rene König<br>"
             "<p><author>Author: Karsten Brandt</author>",
        "de:  <h3>Hebt Parts mit einem gegebenen Value hervor.</h3>\n"
             "Dieses ULP arbeitet aus Boards oder Schematics heraus.<br>"
			 "Diese ULP funktioniert mit Eagle 7 (getested mit 7.5.0<). Nicht getested mit Eagle 6!<br>"
			 "Modifizierte Version von Rene König<br>"
             "<p><author>Autor: Karsten Brandt</author>"

string ULP_KEY = "ShowValues";

#include "config_utils.ulp"

             
enum { ShowTopOnly, ShowBothSides, ShowBottomOnly };
enum { ShowThisPage, ShowOnAllPages };

string strTexts[] =
{
    "en\v"
    "de\v"
    ,
    ";This ULP requires a board or a schematic. Funktionier mit Eagle 7 (getested mit 7.5.0). Nicht getested mit Eagle 6!\v"
    ";Dieses Ulp funktioniert nur in Boards und Schematics. Works with Eagle 7 (tested with 7.5.0). Not tested with Eagle 6!\v"
    ,
    "Please type in the value you want to highlight.\v"
    "Geben Sie den hervorzuhebenden Value ein.\v"
    ,
    ";No elements found with value \"%s\".\v"
    ";Es wurden keine Elemente mit dem Value \"%s\" gefunden.\v"
};


string strMessage;
string strScript;
int foundPartCount = 0;
int showPartsOnSides = ShowBothSides;
int showPartsOnPages = ShowOnAllPages;
string command;

string get_ulp_name(void) 
{
    string s = strsub(argv[0], 0, strlen(argv[0])-4);
    string p = s;
    char c = '/';
    int pos = strrchr(s, c);
    if (pos >= 0) {
        p = strsub(s, pos + 1);
    }
    return p;
}

string Translate(string src)
{
    string strLoc = lookup(strTexts, src, strstr(strTexts[0], language()) / 3, '\v');
    return((strLoc != "") ? strLoc : src);
}

string InputBoxPCB(string strPrompt, string strDefault)
{
    string strReturn = strDefault;
    int nResult = dlgDialog("Show parts with values")
    {
        dlgGridLayout
        {
            dlgCell(0, 0)
            {
                dlgHBoxLayout
                {
                    dlgLabel(strPrompt);
                    dlgSpacing(20);

                    dlgGroup("Show on side(s):") {
                        dlgRadioButton("&Top", showPartsOnSides);
                        dlgRadioButton("&Both", showPartsOnSides);
                        dlgRadioButton("&Bottom", showPartsOnSides);
                    } 
                    
                    dlgVBoxLayout
                    {
                        dlgPushButton("+OK") dlgAccept();
                        dlgPushButton("Cancel") dlgReject();
                    }
                }
            }
            
            dlgCell(1, 0)
            {
                dlgStringEdit(strReturn);
            }
        }
    };

    return((nResult > 0) ? strReturn : "");
}

string InputBoxSCH(string strPrompt, string strDefault)
{
    string strReturn = strDefault;
    int nResult = dlgDialog("Show parts with values")
    {
        dlgGridLayout
        {
            dlgCell(0, 0)
            {
                dlgHBoxLayout
                {
                    dlgLabel(strPrompt);
                    dlgSpacing(20);

                    dlgGroup("Scope:") {
                        dlgRadioButton("&This page", showPartsOnPages);
                        dlgRadioButton("&All pages", showPartsOnPages);
                    } 
                    
                    dlgVBoxLayout
                    {
                        dlgPushButton("+OK") dlgAccept();
                        dlgPushButton("Cancel") dlgReject();
                    }
                }
            }
            
            dlgCell(1, 0)
            {
                dlgStringEdit(strReturn);
            }
        }
    };

    return((nResult > 0) ? strReturn : "");
}

string strreplace(string original, string toReplace, string replaceWith)
{
    string ret = "";
    string left = original;
    while (strstr(left, toReplace) >= 0) {
        ret += strsub(left, 0, strstr(left, toReplace));
        ret += replaceWith;
        left = strsub(left, strstr(left, toReplace) + strlen(toReplace));
    }
    ret += left;
    return ret;
}


void addFoundPart(string partName) 
{
    if (foundPartCount == 0) {
        sprintf(command, "show %s ", partName);
    } else {
        sprintf(command, "%s %s ", command, partName);
    }
    foundPartCount++;
}

void checkPartName(string value, string partName, string searchString)
{
    int useRegexp = ((strchr(searchString, '*') != -1) | (strchr(searchString, '?') != -1)) ? 1 : 0;
    if (useRegexp) {
        searchString = strreplace(searchString, "*", "([a-zA-Z0-9]*)");
        searchString = strreplace(searchString, "?", "([a-zA-Z0-9]{1})");
        int matchPos = strxstr(value, searchString);
        if (matchPos != -1)
            addFoundPart(partName);
    } else {
        if ((strlwr(value) == strlwr(searchString)))
            addFoundPart(partName);
    }
}

if (board) board(B)
{
    showPartsOnSides = cfgget_int("pcb_side", ShowBothSides);
    if (showPartsOnSides > ShowBottomOnly)
        showPartsOnSides = ShowBothSides;
  
    string strValue = "";
    if (argc == 1) {
        // No command line arguments, start the GUI
        strValue = InputBoxPCB(Translate("Please type in the value you want to highlight."), cfgget_string("pcb_value", ""));
    } else if (argc >= 2){
        // command line arguments are handled in the following way:
        // first argument: part value, 
        // second (optional): side name {top,bottom}
        strValue = argv[1];
        showPartsOnSides = ShowBothSides;
        if (argc == 3) {
            strValue = argv[1];
            if (strlwr(argv[2]) == "top") {
                showPartsOnSides = ShowTopOnly;
            } else if (strlwr(argv[2]) == "bottom" || strlwr(argv[2]) == "bot") {
                showPartsOnSides = ShowBottomOnly;
            }
        } else if (argc > 3) {
            sprintf(strMessage, "!Too many arguments passed: %d\n"
                                "Command line call syntax for running in the board editor:\n"
                                "RUN show_values.ulp <part_name> [top|bottom]\n"
                                "The [top|bottom] argument is optional", argc - 1);
            dlgMessageBox(strMessage);
            exit(EXIT_FAILURE);
        }
    }

    
    if(strValue == "")
        exit(EXIT_SUCCESS);
    cfgset_string("pcb_value", strValue);
    cfgset_int("pcb_side", showPartsOnSides);
    
    B.elements(E) {
        if (showPartsOnSides != ShowBothSides) {
            if (showPartsOnSides == ShowTopOnly && E.mirror != 0)
                continue;
            
            if (showPartsOnSides == ShowBottomOnly && E.mirror == 0)
                continue;
        }
        
        if (!E.populate)
            continue;
        
        checkPartName(E.value, E.name, strValue);
    }

    if (foundPartCount == 0) {
        sprintf(strMessage, Translate(";No elements found with value \"%s\""), strValue);
        if (showPartsOnSides != ShowBothSides)
            sprintf(strMessage, "%s on layer: %s", strMessage, showPartsOnSides == ShowTopOnly ? "TOP" : "BOTTOM");
        dlgMessageBox(strMessage);
        exit(EXIT_FAILURE);
    }
    sprintf(command, "%s @", command);
    exit(command);
}
else if(sheet) sheet(currentSheet)
{
    string schName;
    schematic(SCH)
    {
        schName = SCH.name;
    }
    
    string intVal;
    showPartsOnPages = cfgget_int("sch_pages", ShowOnAllPages);
    if (showPartsOnPages > ShowOnAllPages)
        showPartsOnPages = ShowOnAllPages;

    string strValue;
    if (argc == 1) {
        // No command line arguments, start the GUI
        strValue = InputBoxSCH(Translate("Please type in the value you want to highlight."),  cfgget_string("sch_value", ""));
    } else if (argc == 2){
        // command line arguments are handled in the following way:
        // first argument: part value, 
        strValue = argv[1];
    } else {
        sprintf(strMessage, "!Too many arguments passed: %d\n"
                            "Command line call syntax for running in the schematic editor:\n"
                            "RUN show_values.ulp <part_name>\n", argc - 1);
        dlgMessageBox(strMessage);
        exit(EXIT_FAILURE);
    }
    

    if (strValue == "")
        exit(EXIT_SUCCESS);

    cfgset_string("sch_value", strValue);
    cfgset_int("sch_pages", showPartsOnPages);

    if (showPartsOnPages == ShowOnAllPages) {
        schematic(SCH) {
            SCH.sheets(S) {
                S.parts(P) {
                    checkPartName(P.value, P.name, strValue);
                }
            }
        }
    } else {
        currentSheet.parts(P) {
            checkPartName(P.value, P.name, strValue);
        }
    }

    if (foundPartCount == 0) {
        if (showPartsOnPages == ShowOnAllPages) {
            sprintf(strMessage, Translate(";No elements found with value \"%s\"."), strValue);
        } else if  (showPartsOnPages == ShowThisPage) {
            sprintf(strMessage, Translate(";No elements found with value \"%s\" on the current sheet."), strValue);
        }
        dlgMessageBox(strMessage);
        exit(EXIT_FAILURE);
    }
    sprintf(command, "%s @", command);
    exit(command);
}
else
{
    dlgMessageBox(Translate(";This ULP can only run from the a board or a schematic."));
}
